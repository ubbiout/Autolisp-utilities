(defun c:findename ( / ss ename want i sf)
  (setq ss (ssget "_X" '((0 . "MAPS_SOLID")))
				i 0
				ssf (ssadd)
				want "<Entity name: 2915fa9ea30>")
	(princ want)(princ "\n")
  (repeat (sslength ss)
    (setq ename (ssname ss i) )
		(princ i )(princ ename)(princ "\n")
	  (if (= i 42)
			(progn
			  (prompt "\n woah")
		  	(princ i )(princ ename)
			  (ssadd ename ssf)
			)
		)
		(setq i (+ i 1) )
	)
	(sssetfirst nil ssf)
	(princ)
)

(defun c:elistquery ( / code ename ss sslen result closedlist )
  (setq ;code (getint "\nAssoc code to query: ")
        code 1000 ;;set what dxf code is returned
        ss (ssget)
        sslen (sslength ss)
        i 0
        closedlist '() )
  (while (< i sslen  )
    (setq ename (ssname ss i)
          result (assoc code (entget ename))
          xdata (assoc -3 (entget ename '("*"))) )
    (if (not (= result ""))
      (progn
		    (if (not (member result closedlist) ) ;;only outputs unique values
		      (progn
            ;;(prompt "\nAssoc ")(princ code)(prompt ": ")
		        (print result) (princ " ")
		        (setq closedlist (append closedlist (list result)) )
		      )
          ;;(princ "..not member..")
		    )
      )
      ;;(princ "..was blank..")
    )
    (print xdata) (princ " ")
    (setq i (+ i 1) )
  )
  (princ)
)

(defun C:Layrinfo ( / acadobject activedocument LayerCollection
                      layname ename layweight idk)
	(vl-load-com)
	(setq acadobject (vlax-get-Acad-Object) )
	(setq activedocument (vla-get-activedocument acadobject) )
	(setq LayerCollection (vla-get-layers activedocument) )
	(vlax-for each LayerCollection
    (setq layname (vla-get-Name each) )
    (setq layweight (vla-get-LineWeight each) )
    (setq idk 0 );; value that corresponds to (assoc 8 (entget someEntitysEname))
    (prompt "\nLayer name: ")(princ layname)
    (prompt " Lineweight: ")(princ layweight)
    (prompt " corresponding assoc 8 value: ")(princ idk)
	)
)
